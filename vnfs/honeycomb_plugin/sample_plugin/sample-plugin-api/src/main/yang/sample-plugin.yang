//*************************************************************//
//
// Copyright © 2017 AT&T Intellectual Property. All rights reserved.
//
// Licensed under the Apache License, Version 2.0 (the "License");
// you may not use this file except in compliance with the License.
// You may obtain a copy of the License at
// http://www.apache.org/licenses/LICENSE-2.0
// 
// Unless required by applicable law or agreed to in writing, software
// distributed under the License is distributed on an "AS IS" BASIS,
// WITHOUT WARRANTIES OR CONDITIONS OF ANY KIND, either express or implied.
// See the License for the specific language governing permissions and
// limitations under the License.
//
//******************************************************************


module sample-plugin {

    yang-version 1;
    namespace "urn:opendaylight:params:xml:ns:yang:sample-plugin";
    prefix "sample-plugin";

    import ietf-inet-types { prefix "inet"; }

    description
        "This YANG module defines the generic configuration and
        operational data for sample-plugin in VPP";

    revision "2016-09-18" {
        description "Initial revision of sample-plugin model";
    }

    container sample-plugin {
        uses sample-plugin-params;
        description "Configuration data of sample-plugin in Honeycomb";

        // READ
        // curl -u admin:admin http://localhost:8181/restconf/config/sample-plugin:sample-plugin

        // WRITE
        // curl http://localhost:8181/restconf/operational/sample-plugin:sample-plugin

    }

    container sample-plugin-state {
        config false;
        uses sample-plugin-params;
        description "Operational data of sample-plugin persisted in VPP";

        // READ
        // curl -u admin:admin  http://localhost:8181/restconf/operational/sample-plugin:sample-plugin-state
    }

    grouping sample-plugin-params {
        container pg-streams {
            list pg-stream {

                key id;
                leaf id {
                    type string;
                }

                leaf is-enabled {
                  type boolean;
                }
            }
        }
    }

    notification sample-notification {
        leaf content {
            type string;
        }
    }
}
